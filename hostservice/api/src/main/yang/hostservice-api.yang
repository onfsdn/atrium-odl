/*
 * Copyright (c) 2015 Wipro Ltd. and others.  All rights reserved.
 *
 * This program and the accompanying materials are made available under the
 * terms of the Eclipse Public License v1.0 which accompanies this distribution,
 * and is available at http://www.eclipse.org/legal/epl-v10.html
 */
module hostservice-api {
    yang-version 1;
    namespace "urn:opendaylight:params:xml:ns:yang:hostservice:api";
    prefix "hostservice-api";
	
	import yang-ext {
    	prefix ext;
    	revision-date "2013-07-09";
  	}
	
    import ietf-inet-types {
        prefix inet;
        revision-date 2010-09-24;
    }

    import ietf-yang-types {
        prefix yang;
        revision-date 2010-09-24;
    }
    
    import ethernet-packet {
    	prefix ethernet;
    	revision-date 2014-05-28;
  	}
	
	import network-topology {prefix "topo"; revision-date "2013-10-21"; }
	
    import config { prefix config; revision-date 2013-04-05; }
	
    import opendaylight-inventory {
        prefix inv;
        revision-date 2013-08-19;
    }
    
    import atriumutil-api {
        prefix atriumutil-api;
        revision-date 2015-07-25;
    }
    
    revision "2015-07-25" {
        description "Initial revision of hostservice model";
    }
    
    identity hostservice-api {
        base "config:service-type";
        config:java-class "org.opendaylight.atrium.hostservice.api.HostService";
    }
    
    typedef host-id {
        type string;
    }
    
    
    container addresses {
        list address{
	    	uses atriumutil-api:interfaceAddress;
	    	key "ipAddress";
	    	leaf dpid{
	    		description "Specifies the dpid";
	    		config "true";
	    		type string;
	    	}
	    	
	    	leaf mac {
		         	description "Specifies the node id of the DP switch";
		         	config "true";
		        	type yang:mac-address;
	  	    }
	  	    leaf vlan {
		         	description "Specifies the vlan id of the DP switch";
		         	config "true" ;
		        	type uint16;
		    }
	}
    }
    
    grouping address-node-connector {
	    list connector-address {
		      key id;
		      leaf id {
		        description "A 64-bit key for this observation. This is opaque and should not be interpreted.";
		        type uint64;
		      }
		      leaf mac {
		        type yang:mac-address;
		        description "MAC address";
		      }
		      leaf ip {
		        type inet:ip-address;
		        description "IPv4 or IPv6 address";
		      }
		      leaf vlan {
		        type ethernet:vlan-id;
		        description "VLAN id";
		      }
		      leaf first-seen {
		        type int64;
		        description "Timestamp (number of ms since January 1, 1970, 00:00:00 GMT) of observing this address for the first time";
		      }
		      leaf last-seen {
		        type int64;
		        description "The most recent timestamp (tnumber of ms since January 1, 1970, 00:00:00 GMT) of observing this address";
		      }
	    }
  	}
  
	  grouping host {
	        description "List of addresses and attachment points";
	        uses address-node-connector;
	        leaf id {
	            type host-id;
	        }
	        list attachment-points {
	            description "the assumption is that all address can be reached at all attachment points";
	            uses topo:tp-attributes;
	            key tp-id;
	            leaf corresponding-tp {
	                type topo:tp-ref;
	            }
	            leaf active {
	                type boolean;
	            }
	        }
	    }

    augment "/topo:network-topology/topo:topology/topo:node" {
        ext:augment-identifier "host-node";
        uses host;
    }

  augment "/inv:nodes/inv:node/inv:node-connector" {
    	ext:augment-identifier "address-capable-node-connector";
    	uses address-node-connector;
  }
}
