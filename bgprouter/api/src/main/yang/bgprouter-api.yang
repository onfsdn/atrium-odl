/*
 * Copyright (c) 2015 Wipro Ltd. and others.  All rights reserved.
 *
 * This program and the accompanying materials are made available under the
 * terms of the Eclipse Public License v1.0 which accompanies this distribution,
 * and is available at http://www.eclipse.org/legal/epl-v10.html
 */
module bgprouter-api {
    yang-version 1;
    namespace "urn:opendaylight:params:xml:ns:yang:bgprouter:api";
    prefix "bgprouter-api";
    
    
    import config { prefix config; revision-date 2013-04-05; }
        
    description
        "Service definition for bgp application project";

    revision "2015-07-25" {
        description "Initial revision of bgprouter model";
    }
    
    identity hostservice-api {
        base "config:service-type";
        config:java-class "org.opendaylight.atrium.bgprouter.api.IBgpRouter";
    }
    
}
