/*
 * Copyright (c) 2015 Wipro Ltd. and others.  All rights reserved.
 *
 * This program and the accompanying materials are made available under the
 * terms of the Eclipse Public License v1.0 which accompanies this distribution,
 * and is available at http://www.eclipse.org/legal/epl-v10.html
 */
module bgprouter-impl {
    yang-version 1;
    namespace "urn:opendaylight:params:xml:ns:yang:bgprouter:impl";
    prefix "bgprouter-impl";

    import config { prefix config; revision-date 2013-04-05; }
    import opendaylight-md-sal-binding { prefix md-sal-binding; revision-date 2013-10-28;}
    import bgprouter-api { prefix bgprouter-api; revision-date 2015-07-25;}
    import routingconfig-api { prefix routingconfig-api; revision-date 2015-07-25;}
    import routingservice-api { prefix routingservice-api; revision-date 2015-07-25;}
    import hostservice-api { prefix hostservice-api; revision-date 2015-07-25;}
    
    description
        "Service definition for bgp application impl project";

    revision "2015-07-25" {
        description
            "Initial revision";
    }

    identity bgprouter-impl {
        base config:module-type;
		config:java-name-prefix BgpRouterImpl;
    }

    augment "/config:modules/config:module/config:configuration" {
        case bgprouter-impl {
            when "/config:modules/config:module/config:type = 'bgprouter-impl'";
            container broker {
                uses config:service-ref {
                    refine type {
                        mandatory true;
                        config:required-identity md-sal-binding:binding-broker-osgi-registry;
                    }
                }
            }
            container data-broker {
                uses config:service-ref {
                    refine type {
                        mandatory false;
                        config:required-identity md-sal-binding:binding-async-data-broker;
                    }
                }
            }
            container routingconfig {
                uses config:service-ref {
                    refine type {
                        mandatory true;
                        config:required-identity routingconfig-api:routingconfig-api;
                    }
                }
            } 
            container routingservice {
                uses config:service-ref {
                    refine type {
                        mandatory true;
                        config:required-identity routingservice-api:routingservice-api;
                    }
                }
            }
            container notification-service {
        		uses config:service-ref {
          			refine type {
            			mandatory true;
            			config:required-identity md-sal-binding:binding-notification-service;
          			}
        		}
      		}
            container rpc-registry {
                uses config:service-ref {
                    refine type {
                        mandatory true;
                        config:required-identity md-sal-binding:binding-rpc-registry;
                    }
                }
            }            	
      		container hostservice {
                uses config:service-ref {
                    refine type {
                        mandatory true;
                        config:required-identity hostservice-api:hostservice-api;
                    }
                }
            }                    
        }
    }
}
