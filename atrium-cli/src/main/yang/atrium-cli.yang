/*
 * Copyright (c) 2015 Wipro Ltd. and others.  All rights reserved.
 *
 * This program and the accompanying materials are made available under the
 * terms of the Eclipse Public License v1.0 which accompanies this distribution,
 * and is available at http://www.eclipse.org/legal/epl-v10.html
 */
module atrium-cli {
    yang-version 1;
    namespace "urn:opendaylight:params:xml:ns:yang:atrium-cli:impl";
    prefix "atrium-cli";

    import config { prefix config; revision-date 2013-04-05; }
    import opendaylight-md-sal-binding { prefix md-sal-binding; revision-date 2013-10-28;}
    
    description
        "Service definition for atrium cli impl project";

    revision "2015-07-25" {
        description
            "Initial revision";
    }

    identity atrium-cli {
        base config:module-type;
		config:java-name-prefix AtriumCliImpl;
    }

    augment "/config:modules/config:module/config:configuration" {
        case atrium-cli {
            when "/config:modules/config:module/config:type = 'atrium-cli'";
            container broker {
                uses config:service-ref {
                    refine type {
                        mandatory true;
                        config:required-identity md-sal-binding:binding-broker-osgi-registry;
                    }
                }
            }
            container data-broker {
                uses config:service-ref {
                    refine type {
                        mandatory false;
                        config:required-identity md-sal-binding:binding-async-data-broker;
                    }
                }
            }                  
        }
    }
}
