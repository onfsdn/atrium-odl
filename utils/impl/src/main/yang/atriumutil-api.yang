/*
 * Copyright (c) 2015 Wipro Ltd. and others.  All rights reserved.
 *
 * This program and the accompanying materials are made available under the
 * terms of the Eclipse Public License v1.0 which accompanies this distribution,
 * and is available at http://www.eclipse.org/legal/epl-v10.html
 */
module atriumutil-impl {
	yang-version 1;
    namespace "urn:opendaylight:params:xml:ns:yang:atriumutil:impl";
    prefix "atriumutil-impl";

    description
        "Service definition for atriumutil impl project";

    revision "2015-07-25" {
        description
            "Initial revision";
    }
}
