/*
 * Copyright (c) 2015 Hewlett-Packard Development Company, L.P. and others.  All rights reserved.
 *
 * This program and the accompanying materials are made available under the
 * terms of the Eclipse Public License v1.0 which accompanies this distribution,
 * and is available at http://www.eclipse.org/legal/epl-v10.html
 */
module didm-device-types {

    namespace "urn:opendaylight:params:xml:ns:yang:didm:identification:devicetypes";
    prefix dt;

    import didm-identification { prefix id; revision-date "2015-02-02"; }

    description "YANG model for storing device type information in the MD-SAL data store";

    revision "2015-02-02" {
        description "Initial implementation of data store container to hold device type information.";
    }

    container device-types {
        list device-type-info {
            key "device-type";

            leaf device-type {
                type identityref {
                    base id:device-type-base;
                }
                description "identifier for a list entry, the device type name.";
            }

            /* leaf openflow-manufacturer {
                type string;
                description "The openflow manufacturer of the device.";
            } */
            
            leaf-list openflow-manufacturer{
                type string;
                description "List of manufacturer.";
            }

            leaf-list openflow-hardware {
                type string;
                description "The openflow hardware of the device.";
            }

            leaf-list sysoid {
                type string;
                description "The SNMP sysObjectId that uniquely identifies the device";
            }
        }
    }
}
